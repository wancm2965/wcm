Q931-CONFIGURATION ::=

BEGIN

-- This ASN.1 file contains the settings of the Q931 configuration

IMPORTS
        TransportAddress,
        ReleaseCompleteReason
    FROM H323-MESSAGES;


-- This type is used by both Q931 and RAS configuration trees for their multi-homed addresses.
ListeningAddress ::= SEQUENCE
{
    address     TransportAddress,
    scopeId     INTEGER (0..4294967295) OPTIONAL -- This field is mandatory when using IPv6
}





-- ***********************************************************************************************
--
--                                  Q931 related configuration
--
-- ***********************************************************************************************

Q931Configuration ::= SEQUENCE
{
    responseTimeOut                 INTEGER (0..200),  -- in seconds
    connectTimeOut                  INTEGER (0..20000), -- in seconds
    callSignalingPort               INTEGER (0..65535),
    maxCalls                        INTEGER (0..65535),
    manualAccept                    NULL OPTIONAL,
    notEstablishControl             NULL OPTIONAL,
    h245Tunneling                   NULL OPTIONAL,
    earlyH245                       NULL OPTIONAL,
    autoAnswer                      NULL OPTIONAL,
    ...
    manualCallProceeding            NULL OPTIONAL,
    overlappedSending               NULL OPTIONAL,   -- default not used
    t302                            INTEGER (0..200) OPTIONAL, -- overlapsending timeout on the incoming side in seconds
    t304                            INTEGER (0..200) OPTIONAL, -- overlapsending timeout on the outgoing side in seconds
    t310                            INTEGER (0..20000) OPTIONAL, -- Timeout between incoming CallProceeding and Alerting or Connect messages. in seconds (default is to use connectTimeOut instead)
    t322                            INTEGER (0..3600) OPTIONAL, -- StatusEnquiry timeout in seconds (default is 4 seconds)
    busyCause                       INTEGER(0..127) OPTIONAL,
    busyReason                      ReleaseCompleteReason OPTIONAL
    useAnnexE                       SEQUENCE
    {
        defaultProtocol                 BOOLEAN OPTIONAL,
        protocolPreference              CHOICE
        {
            annexE                          NULL,
            tpkt                            NULL,
            raceAnnexE                      NULL,
            raceTPKT                        NULL
        } OPTIONAL,

        t_R1                            INTEGER (1..10000) OPTIONAL, -- timeout for first msg (in millis)
        t_R2                            INTEGER (1..10000) OPTIONAL, -- timeout for second and more msg (in millis)
        n_R1                            INTEGER (1..50) OPTIONAL,    -- retries for msg
        t_IMA1                          INTEGER (1..20000) OPTIONAL,   -- timeout for keep-alive (in milliseconds)
        n_IMA1                          INTEGER (1..50) OPTIONAL,    -- retries for keep-alive
        t_DT                            INTEGER (1..200) OPTIONAL    -- percent to add to t_R1 for request/reply interval
    } OPTIONAL,
    diffSrcAddressInSetupAndARQ     NULL OPTIONAL,
    postControlDisconnectionDelay   INTEGER (0..65535) OPTIONAL, -- time to wait for the RELEASE COMPLETE after control was disconnected by remote party
    keepCallOnQ931Close             NULL OPTIONAL, -- The call should not be dropped when Q931 connection dropped
    multipleCallSignalingAddresses  SEQUENCE OF ListeningAddress OPTIONAL,
    maxConnectingCalls              INTEGER (0..65535) OPTIONAL -- default value is Q931.maxCalls
}



END
