STACK-DATABASE-PROPERTIES DEFINITIONS AUTOMATIC TAGS ::=
BEGIN


IMPORTS
        TransportAddress,
        RasMessage
    FROM H323-MESSAGES
        Q931Message
    FROM Q931-PRIVATE-ASN;





-- Property DB for a RAS transaction
-- This is the structure of the txProperty root of a RAS transaction.
-- It can be accessed by the application to chech values inside the request and
-- response messages.
RasApplicationMessage ::= SEQUENCE
{
    address                 TransportAddress OPTIONAL,       -- RAS Address of other side in transaction
    request                 RasMessage OPTIONAL,             -- Request message
    response                RasMessage OPTIONAL,             -- Response message
    progress                RasMessage OPTIONAL,             -- RIP message
}


-- Property DB for a call
-- This is the structure of the property root of a call element.
-- It can be accessed by the application to chech values inside various
-- messages that were sent and received.
Q931ApplicationMessage ::= SEQUENCE
{
    setup                   Q931Message OPTIONAL,
    callProceeding          Q931Message OPTIONAL,
    alerting                Q931Message OPTIONAL,
    connect                 Q931Message OPTIONAL,
    releaseComplete         Q931Message OPTIONAL,
    facility                Q931Message OPTIONAL,
    status                  Q931Message OPTIONAL,
    statusEnquiry           Q931Message OPTIONAL,
    setupAck                Q931Message OPTIONAL,
    information             Q931Message OPTIONAL,
    progress                Q931Message OPTIONAL,
    notify                  Q931Message OPTIONAL
}


END
