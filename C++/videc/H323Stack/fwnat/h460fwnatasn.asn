H460-FWNAT-OBJECT DEFINITIONS AUTOMATIC TAGS ::=
BEGIN

IMPORTS
		TimeToLive,
		TransportAddress,
		CallIdentifier
	FROM H323-MESSAGES;


-- EXPORTS All

IncomingCallIndication ::= SEQUENCE
{
        callSignallingAddress           TransportAddress,       -- Q931Listening address of GK
        callID                          CallIdentifier,
        ...
}


TraversalParameters		::=SEQUENCE
{
	multiplexedMediaChannel             TransportAddress            OPTIONAL,
	multiplexedMediaControlChannel      TransportAddress            OPTIONAL,
	multiplexID                         INTEGER (0..4294967295)     OPTIONAL,
	keepAliveChannel                    TransportAddress            OPTIONAL,
	keepAlivePayloadType                INTEGER (0..127)            OPTIONAL,
	keepAliveInterval                   TimeToLive                  OPTIONAL,
	...										
}

END     -- End of H460-FWNAT-OBJECT DEFINITIONS
